/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Tools

section "Tool Requirements" {

    section "PlantUML Parser" {

        section "General" {

            ToolRequirement ArchitectureModelingSyntax {
                description = '''All PlantUML diagrams shall be checked automatically for syntactical correctness during build process and shall fail errors are detected'''
            }

        }

        section "Component Diagram" {

            ToolRequirement ArchitectureModelingComponentContentSEooC {
                description = '''For PlantUML Component Diagrams the contributor shall define SEooC elements according to the notation::
                package "SEooC" as SampleSEooC <<SEooC>>'''
            }

            ToolRequirement ArchitectureModelingComponentContentComponent {
                description = '''For PlantUML Component Diagrams the contributor shall define Software Components according to the notation::
                component "SampleComponent" as CompSample <<component>>'''
            }

            ToolRequirement ArchitectureModelingComponentContentSWUnit {
                description = '''For PlantUML component diagrams the contributor shall define software units according to the notation::
                component "Sample Unit" as UnitSample <<unit>>'''
            }

            ToolRequirement ArchitectureModelingComponentContentAbstractInterface {
                description = '''For PlantUML component diagrams the contributor shall define abstract interfaces according to the notation::
                interface "Sample Interface" as IfSampleInterface'''
            }

            ToolRequirement ArchitectureModelingComponentHierarchySEooC {
                description = '''The tooling shall verify during traceability build that a contributor defined the hierarchy within a SEooC via nesting::
                - SEooC { Component[1..n] }'''
            }

            ToolRequirement ArchitectureModelingComponentHierarchyComponent {
                description = '''The tooling shall verify during traceability build that a contributor defined the hierarchy within a software component via nesting::
                - Component {
                Component[1..n]
                Unit[1..n]
                }'''
            }

            ToolRequirement ArchitectureModelingComponentInteract {
                description = '''The tooling shall verify during traceability build that a contributor defined the relations between software units via interfaces::
                - Unit --() Interface : provides
                - Unit --( Interface : requires'''
            }

        }

        section "Sequence Diagram" {

            ToolRequirement ArchitectureModelingSequenceContentActors {
                description = '''The tooling shall verify during traceability build that a contributor defined actors in sequence diagrams according to the notation::
                actor "Sample Actor" as ActorSample'''
            }

            ToolRequirement ArchitectureModelingSequenceContentSWUnits {
                description = '''The tooling shall verify during traceability build that a contributor defined software units in sequence diagrams according to the notation::
                participant "Sample Unit" as UnitSample <<unit>>'''
            }

            ToolRequirement ArchitectureModelingSequenceContentMessages {
                description = '''The tooling shall verify during traceability build that a contributor defined messages in sequence diagrams according to the notation::
                UnitSample -> UnitAnotherSample : MethodA()'''
            }

            ToolRequirement ArchitectureModelingSequenceContentActivity {
                description = '''The tooling shall verify during traceability build that a contributor defined activity bars in sequence diagrams to indicate concurrency according to the notation::
                activate UnitSample / deactivate UnitSample'''
            }

            ToolRequirement ArchitectureModelingSequenceCreate {
                description = '''The tool shall resolve a message ending in `**` as a create message and a message ending in `!!` as a delete message.'''
            }

            ToolRequirement ArchitectureModelingSequenceMessageKinds {
                description = '''The tool shall resolve a message with a dashed line as a reply, a message with an `>>` arrowhead as an asynchronous call, and any other message as a synchronous call.'''
            }

        }

        section "Group Resolution" {

            ToolRequirement GroupResolutionInputGroup {
                description = '''The tool shall resolve all input files of one invocation, whether given by `--file` or `--folders`, per diagram kind as one group.'''
            }

            ToolRequirement GroupResolutionInputExtension {
                description = '''The tool shall report an error for an input file whose extension is not `.puml`.'''
            }

            ToolRequirement GroupResolutionDuplicateInput {
                description = '''The tool shall report an error when one invocation names the same input file more than once.'''
            }

            ToolRequirement GroupResolutionImplicitParent {
                description = '''In component and class diagrams, when a top-level element with a body matches a nested declaration in another file of the group, the tool shall resolve the top-level element as that nested declaration, so that its children belong to the nested declaration.'''
            }

            ToolRequirement GroupResolutionImplicitParentEligibility {
                description = '''In component and class diagrams, a top-level element without a body, or whose element type or stereotype differs from the nested declaration, shall stay a top-level element.'''
            }

            ToolRequirement GroupResolutionAmbiguousImplicitParent {
                description = '''The tool shall report `AmbiguousImplicitParent` when a top-level element with a body matches more than one nested declaration in the other files of the group.'''
            }

            ToolRequirement GroupResolutionImplicitParentCycle {
                description = '''The tool shall report `ImplicitParentCycle` when resolving top-level elements as nested declarations would make an element its own ancestor.'''
            }

            ToolRequirement GroupResolutionRelationEndpoint {
                description = '''In component and class diagrams, the tool shall resolve a relation endpoint to the declaration in the file of the relation when that file has one, and otherwise to the matching element of another file of the group.'''
            }

            ToolRequirement GroupResolutionAmbiguousReference {
                description = '''The tool shall report `AmbiguousReference` when a relation endpoint is not declared in the file of the relation and matches more than one element in the other files of the group.'''
            }

            ToolRequirement GroupResolutionRelationSource {
                description = '''In component and class diagrams, the tool shall report `CrossFileRelationSource` when the source of a relation is not declared in the file of the relation. An undirected component relation whose target is declared in that file belongs to that target instead.'''
            }

            ToolRequirement GroupResolutionSequenceParticipant {
                description = '''In sequence diagrams, the tool shall resolve a participant used in one file to the declaration in the file itself when it has one, and otherwise to the declaration in another file of the group.'''
            }

        }
    }
}
