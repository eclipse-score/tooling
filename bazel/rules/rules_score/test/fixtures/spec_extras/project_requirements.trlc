/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

package TestFixtures

import ExtraModel
import ScoreReq

ScoreReq.AssumedSystemReq ASR_TEST_001 {
    description = "Input system-level requirement for spec_extras test"
    rationale = "Needed to satisfy derived_from constraints"
    safety = ScoreReq.Asil.B
    version = 1
}

ExtraModel.ProjectSpecificReq PROJ_REQ_001 {
    description = "Requirement using a type from spec_extras."
    safety = ScoreReq.Asil.B
    derived_from = [ASR_TEST_001@1]
    version = 1
    project_id = "TEST"
}
