/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

// The root cause is assessed by a component requirement.
package CompReqMeasureAssessments

import ScoreReq
import AouRootCauseFta
import CompReqMeasure

ScoreReq.RootCauseAssessment WrongConfigurationAssessed {
    root_causes = [AouRootCauseFta.UserProvidedWrongConfiguration]
    measures = [CompReqMeasure.ValidatesConfiguration@1]
    safety = ScoreReq.Asil.B
    rationale = "The component validates the configuration."
    version = 1
}
