/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

package CompReqMeasure

import ScoreReq
import TestSEooC

ScoreReq.CompReq ValidatesConfiguration {
    description = "The component shall validate its configuration"
    safety = ScoreReq.Asil.B
    version = 1
    derived_from = [TestSEooC.FEAT_TEST_001@1]
}
