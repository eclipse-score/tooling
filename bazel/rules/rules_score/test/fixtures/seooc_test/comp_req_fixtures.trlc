/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package SeoocTest

import ScoreReq

ScoreReq.CompReq COMP_001 {
    description  = "The component shall process input data within defined latency bounds"
    safety       = ScoreReq.Asil.QM
    derived_from = [SeoocTest.FEAT_001@1]
    version      = 1
}
