/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package TestComponentChainReceivedAoU

import ScoreReq
import AssumptionsOfUse

ScoreReq.CompReq REQ_COMP_CHAIN_AOU_001 {
    description = "Downstream requirement referencing an AoU that was received by an intermediate dependable_element and chain-forwarded onward (not this element's own AoU, and not a direct dependency of the AoU's original owner)."
    safety = ScoreReq.Asil.B
    derived_from = [AssumptionsOfUse.aou_req__seooc_test__operating_temperature_range@1]
    version = 1
}
