/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

// Fixture exercising the Measure type hierarchy (SafetyMeasure/Mitigation/AoU/
// CompReq): every fault-tree root cause (RootCause) must be addressed by at
// least one concrete measure.
// - SafetyMeasure: abstract, never instantiated directly; only exists so
//   Mitigation and AoU inherit the mandatory ``root_causes`` field.
// - Mitigation: extends SafetyMeasure, adds a mandatory ``justification``
//   explaining why the root cause does not apply in this context.
// - AoU: extends SafetyMeasure; its ``root_causes`` field is mandatory -- an
//   AoU is a preventive measure for the fault-tree root causes it addresses.
// - CompReq (elsewhere): acts as a control measure when its ``derived_from``
//   references a fault-tree RootCause.

package TestSafetyMeasures

import ScoreReq

ScoreReq.FailureMode SomeFailureMode {
    guidewords    = [ScoreReq.Guideword.LossOfFunction]
    failureeffect = "Some effect"
    safety        = ScoreReq.Asil.B
    description   = "A failure mode backing this fixture's fault tree"
    version       = 1
}

ScoreReq.RootCause SomeRootCause {
    title         = "Some root cause"
    diagram       = "n/a"
    line          = 1
    failure_modes = [TestSafetyMeasures.SomeFailureMode]
}

ScoreReq.Mitigation SomeMitigation {
    safety        = ScoreReq.Asil.B
    description   = "Mitigation linked to the FTA RootCause via an explicit root_causes reference"
    justification = "This root cause cannot occur in this context because of an independent design property"
    version       = 1
    root_causes   = [TestSafetyMeasures.SomeRootCause]
}

ScoreReq.AoU SomeAoU {
    safety      = ScoreReq.Asil.B
    description = "An assumption of use that also addresses a fault-tree root cause"
    version     = 1
    root_causes = [TestSafetyMeasures.SomeRootCause]
}
