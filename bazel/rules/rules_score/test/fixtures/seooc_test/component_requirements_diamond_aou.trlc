/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package TestComponentDiamondAoU

import ScoreReq
import AssumptionsOfUse

ScoreReq.CompReq REQ_COMP_DIAMOND_AOU_001 {
    description = "Diamond dependency regression: depends on both the AoU's original owner directly and an intermediate dependable_element that chain-forwards that same AoU. Must resolve without a TRLC duplicate-definition error."
    safety = ScoreReq.Asil.B
    derived_from = [AssumptionsOfUse.aou_req__seooc_test__operating_temperature_range@1]
    version = 1
}
