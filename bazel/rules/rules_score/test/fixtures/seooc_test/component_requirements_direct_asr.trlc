/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

// This fixture demonstrates that a CompReq can be traced directly to an
// AssumedSystemReq, skipping the feature-requirement level entirely.
package TestComponentDirectAsr

import ScoreReq
import TestSEooC

ScoreReq.CompReq REQ_COMP_DIRECT_ASR_001 {
    description = "The mock library shall provide a minimal interface directly satisfying the system-level interface requirement"
    safety = ScoreReq.Asil.B
    derived_from = [TestSEooC.ASR_TEST_001@1]
    version = 1
}
