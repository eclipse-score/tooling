/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package TestComponentChainAoUNegative

import ScoreReq
import AssumptionsOfUse

ScoreReq.CompReq REQ_COMP_CHAIN_AOU_NEG_001 {
    description = "Negative check: references an AoU that was received but NOT selected for chain-forwarding."
    safety = ScoreReq.Asil.B
    derived_from = [AssumptionsOfUse.aou_req__seooc_test__supply_voltage@1]
    version = 1
}
