/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package TestSEooC

import ScoreReq

ScoreReq.FeatReq FEAT_TEST_001 {
    description = "The test component shall provide a mock function interface for unit testing"
    safety = ScoreReq.Asil.B
    derived_from = [TestSEooC.ASR_TEST_001@1]
    version = 1
}
