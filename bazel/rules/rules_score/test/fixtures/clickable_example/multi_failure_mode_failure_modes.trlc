/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MultiFailureModeExampleSafetyAnalysis

import ScoreReq
import package_pub_api

ScoreReq.FailureMode MessageLost {
    guidewords = [ScoreReq.Guideword.LossOfFunction]
    description = "Message is lost in transit"
    failureeffect = "Receiver never gets the message"
    version = 1
    safety = ScoreReq.Asil.B
    interface = [package_pub_api.package_pub_PublicInterface_Send]
}

ScoreReq.FailureMode MessagePartiallyDelivered {
    guidewords = [ScoreReq.Guideword.PartialFunction]
    description = "Message is only partially delivered"
    failureeffect = "Receiver processes incomplete data"
    version = 1
    safety = ScoreReq.Asil.B
    interface = [package_pub_api.package_pub_PublicInterface_Send]
}

ScoreReq.FailureMode MessageCorrupted {
    guidewords = [ScoreReq.Guideword.Corrupted]
    description = "Message content is corrupted in transit"
    failureeffect = "Receiver processes wrong data"
    version = 1
    safety = ScoreReq.Asil.B
    interface = [package_pub_api.package_pub_PublicInterface_Send]
}
