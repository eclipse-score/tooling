/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package DynamicExampleSafetyAnalysis

import ScoreReq
import dynamic_example_api

ScoreReq.FailureMode TaskInterfaceFailure {
    guidewords = [ScoreReq.Guideword.LossOfFunction]
    description = "TaskInterface stops responding"
    failureeffect = "Tasks are never dispatched to the Worker"
    version = 1
    safety = ScoreReq.Asil.B

    interface = [dynamic_example_api.TaskInterface_AssignTask]
}
