/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

// Integration fixture: uses AssumedSystemReq (base model) and ProjectNote
// (extra model) in one file to verify that both RSL files are reachable when
// spec is passed as a list.
package MultiSpecIntTest

import ScoreReq
import ProjectReq

ScoreReq.AssumedSystemReq asr_multi_spec_inttest_001 {
    description = "The system shall support multi-spec requirements models."
    safety      = ScoreReq.Asil.B
    version     = 1
    rationale   = "Validates that the base spec types are accessible when spec is a list."
}

ProjectReq.ProjectNote note_multi_spec_inttest_001 {
    description = "Validates that a type from the extra spec is accessible alongside the base model."
}
