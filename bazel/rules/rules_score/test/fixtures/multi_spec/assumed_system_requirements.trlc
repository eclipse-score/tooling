/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MultiSpecASR

import ScoreReq

ScoreReq.AssumedSystemReq ASR_MULTI_SPEC_001 {
    description = "The system shall provide a minimal interface for multi-spec test fixture validation."
    safety = ScoreReq.Asil.B
    version = 1
    rationale = "Basic system-level requirement for multi-spec test fixture"
}
