/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package MultiSpecComp

import MultiSpecFeat
import ScoreReq

ScoreReq.CompReq COMP_MULTI_SPEC_001 {
    description = "The mock library shall provide mock_function_1 returning 42 for multi-spec fixture validation."
    safety = ScoreReq.Asil.B
    derived_from = [MultiSpecFeat.FEAT_MULTI_SPEC_001@1]
    version = 1
}
