/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package ImageTest

Requirement REQ_with_image {
    description = '''
        The system shall support image rendering in requirements.

        ![System overview](diagrams/overview.svg)
    '''
}

Requirement REQ_with_png_image {
    description = '''
        The system shall support PNG image rendering in requirements.

        ![System overview PNG](diagrams/overview.png)
    '''
}

Requirement REQ_no_image {
    description = "The system shall operate without images."
}
