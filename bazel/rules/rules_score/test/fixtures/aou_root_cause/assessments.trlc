/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

// Regression fixture: the generated fault-tree root cause is assessed by an
// own AoU.
package AouRootCauseAssessments

import ScoreReq
import AouRootCauseFta
import AouRootCauseAous

ScoreReq.RootCauseAssessment WrongConfigurationAssessed {
    root_causes = [AouRootCauseFta.UserProvidedWrongConfiguration]
    measures = [AouRootCauseAous.ConfigurationIsCorrect@1]
    safety = ScoreReq.Asil.B
    rationale = "The user is told to provide a correct configuration."
    version = 1
}
