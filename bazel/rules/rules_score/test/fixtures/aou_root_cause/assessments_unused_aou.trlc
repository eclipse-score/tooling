/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

// Negative fixture: the root cause is assessed, but no assessment lists the
// own AoU `AouRootCauseAous.ConfigurationIsCorrect`.
package AouRootCauseAssessmentsUnusedAou

import ScoreReq
import AouRootCauseFta

ScoreReq.RootCauseAssessment WrongConfigurationAssessed {
    root_causes = [AouRootCauseFta.UserProvidedWrongConfiguration]
    measures = []
    safety = ScoreReq.Asil.B
    rationale = "The root cause cannot occur by design."
    version = 1
}
