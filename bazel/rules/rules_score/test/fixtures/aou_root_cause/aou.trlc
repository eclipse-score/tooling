/*******************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

// Regression fixture: an AoU that an assessment lists as measure of a
// generated fault-tree root cause (see assessments.trlc).
package AouRootCauseAous

import ScoreReq

ScoreReq.AoU ConfigurationIsCorrect {
    description = "The user shall provide a correct configuration"
    safety = ScoreReq.Asil.B
    version = 1
}
