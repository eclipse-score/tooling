/*******************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package TransferFtaSafetyAnalysis

import ScoreReq
import package_pub_api

ScoreReq.FailureMode TopFailure {
    guidewords = [ScoreReq.Guideword.LossOfFunction]
    description = "PublicInterface stops responding"
    failureeffect = "Callers never receive a response"
    version = 1
    safety = ScoreReq.Asil.B
    interface = [package_pub_api.package_pub_PublicInterface_Send]
}
