// GENERATED by puml_cli from FTA diagrams -- do not edit
package transfer_fta_fault_trees_fta

import ScoreReq
import TransferFtaSafetyAnalysis

// shared_fta.puml:20
ScoreReq.RootCause ResourceExhausted {
  title = "The shared resource is exhausted"
  diagram = "shared_fta.puml"
  line = 20
  failure_modes = [TransferFtaSafetyAnalysis.TopFailure]
}

// top_fta.puml:20
ScoreReq.RootCause ServiceCrashes {
  title = "The service crashes"
  diagram = "top_fta.puml"
  line = 20
  failure_modes = [TransferFtaSafetyAnalysis.TopFailure]
}
