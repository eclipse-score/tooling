/*******************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

package AsilUpstream

import ScoreReq

ScoreReq.AssumedSystemReq AsrQm {
    description = "System-level requirement without safety relevance."
    rationale = "Fixture."
    safety = ScoreReq.Asil.QM
    version = 1
}

ScoreReq.AssumedSystemReq AsrB {
    description = "System-level requirement at ASIL B."
    rationale = "Fixture."
    safety = ScoreReq.Asil.B
    version = 1
}

ScoreReq.AssumedSystemReq AsrD {
    description = "System-level requirement at ASIL D."
    rationale = "Fixture."
    safety = ScoreReq.Asil.D
    version = 1
}

ScoreReq.AoU AouB {
    description = "The user shall provide a correct configuration."
    safety = ScoreReq.Asil.B
    version = 1
}

ScoreReq.AoU AouD {
    description = "The user shall provide a correct configuration at ASIL D."
    safety = ScoreReq.Asil.D
    version = 1
}
