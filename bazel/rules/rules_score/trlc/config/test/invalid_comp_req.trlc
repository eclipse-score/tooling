/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

// These CompReq entries intentionally violate the ASIL safety check:
//   "ASIL level of derived requirement must be at least the same as the upstream requirement"
// Running trlc on these files together with valid_asr.trlc and valid_feat_req.trlc
// MUST produce errors.

package AssilCheckInvalidComp

import ScoreReq
import AssilCheckValid

// INVALID: upstream FeatReq (FEAT_VALID_002) is ASIL B, this CompReq is ASIL QM — degraded.
// Expected error on field: safety
ScoreReq.CompReq COMP_INVALID_001 {
    description  = "The component shall implement the communication interface — incorrectly declared at ASIL QM despite ASIL B feature requirement."
    safety       = ScoreReq.Asil.QM
    derived_from = [AssilCheckValid.FEAT_VALID_002@1]
    version      = 1
}

// INVALID: upstream FeatReq (FEAT_VALID_004) is ASIL D, this CompReq is ASIL B — degraded.
// Expected error on field: safety
ScoreReq.CompReq COMP_INVALID_002 {
    description  = "The component shall implement fault-tolerant operation — incorrectly declared at ASIL B despite ASIL D feature requirement."
    safety       = ScoreReq.Asil.B
    derived_from = [AssilCheckValid.FEAT_VALID_004@1]
    version      = 1
}

// INVALID: upstream FeatReq (FEAT_VALID_004) is ASIL D, this CompReq is ASIL QM — degraded.
// Expected error on field: safety
ScoreReq.CompReq COMP_INVALID_003 {
    description  = "The component shall guarantee integrity — incorrectly declared at ASIL QM despite ASIL D feature requirement."
    safety       = ScoreReq.Asil.QM
    derived_from = [AssilCheckValid.FEAT_VALID_004@1]
    version      = 1
}

// INVALID: upstream ASR (ASR_VALID_003) is ASIL D, this CompReq is ASIL B — degraded
// (direct ASR traceability, bypassing feature level).
// Expected error on field: safety
ScoreReq.CompReq COMP_INVALID_004 {
    description  = "The component shall handle system-level fault tolerance — incorrectly declared at ASIL B despite ASIL D ASR."
    safety       = ScoreReq.Asil.B
    derived_from = [AssilCheckValid.ASR_VALID_003@1]
    version      = 1
}
