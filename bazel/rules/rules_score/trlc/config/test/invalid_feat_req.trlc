/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

// These FeatReq entries intentionally violate the ASIL safety check:
//   "ASIL level of derived requirement must be at least the same as the upstream requirement"
// Running trlc on these files together with valid_asr.trlc MUST produce errors.

package AssilCheckInvalidFeat

import ScoreReq
import AssilCheckValid

// INVALID: upstream ASR is ASIL B, this FeatReq is ASIL QM — degraded ASIL.
// Expected error on field: safety
ScoreReq.FeatReq FEAT_INVALID_001 {
    description  = "The component shall report status — incorrectly declared at ASIL QM despite ASIL B upstream."
    safety       = ScoreReq.Asil.QM
    derived_from = [AssilCheckValid.ASR_VALID_002@1]
    version      = 1
}

// INVALID: upstream ASR is ASIL D, this FeatReq is ASIL B — degraded ASIL.
// Expected error on field: safety
ScoreReq.FeatReq FEAT_INVALID_002 {
    description  = "The component shall handle fault-tolerant messages — incorrectly declared at ASIL B despite ASIL D upstream."
    safety       = ScoreReq.Asil.B
    derived_from = [AssilCheckValid.ASR_VALID_003@1]
    version      = 1
}

// INVALID: upstream ASR is ASIL D, this FeatReq is ASIL QM — degraded ASIL.
// Expected error on field: safety
ScoreReq.FeatReq FEAT_INVALID_003 {
    description  = "The component shall guarantee integrity — incorrectly declared at ASIL QM despite ASIL D upstream."
    safety       = ScoreReq.Asil.QM
    derived_from = [AssilCheckValid.ASR_VALID_003@1]
    version      = 1
}
