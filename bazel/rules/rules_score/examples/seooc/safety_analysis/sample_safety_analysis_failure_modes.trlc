/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package SampleLibrary

import ScoreReq
import sample_seooc_api

ScoreReq.FailureMode SampleFailureMode{
    guidewords = [ScoreReq.Guideword.LossOfFunction]
    description = "SampleFailureMode takes over the world"
    failureeffect = "The world as we know it will end"
    version = 1
    safety = ScoreReq.Asil.B
    interface = [sample_seooc_api.safety_software_seooc_example_SampleLibraryAPI_GetNumber]
}

ScoreReq.FailureMode SampleFailureMode2{
    guidewords = [ScoreReq.Guideword.TooLate]
    description = "SampleFailureMode2 responds too late"
    failureeffect = "Downstream consumers time out"
    version = 1
    safety = ScoreReq.Asil.D
    interface = [sample_seooc_api.safety_software_seooc_example_SampleLibraryAPI_GetNumber]
}
