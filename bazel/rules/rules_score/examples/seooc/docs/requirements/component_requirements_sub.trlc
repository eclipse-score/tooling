/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package SampleComponent

import ScoreReq
import SampleSEooC

ScoreReq.CompReq REQ_COMP_006 {
    description = "The numeric value formatter shall convert a validated numeric value manager into a human-readable string representation"
    safety = ScoreReq.Asil.B
    derived_from = [SampleSEooC.FEAT_002@1]
    version = 1
}
