/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package SampleComponent

import ScoreReq
import SampleSEooC

ScoreReq.CompReq REQ_COMP_001 {
    description = "The numeric value management interface shall provide a read operation that returns a uint8_t value"
    safety = ScoreReq.Asil.B
    derived_from = [SampleSEooC.FEAT_001@1]
    version = 1
}

ScoreReq.CompReq REQ_COMP_002 {
    description = "The numeric value management interface shall not be extensible by external code"
    safety = ScoreReq.Asil.B
    derived_from = [SampleSEooC.FEAT_002@1]
    version = 1
}

ScoreReq.CompReq REQ_COMP_003 {
    description = "The numeric value validator shall return a boolean result indicating whether the managed numeric value equals 42"
    safety = ScoreReq.Asil.B
    derived_from = [SampleSEooC.FEAT_003@1]
    version = 1
}

ScoreReq.CompReq REQ_COMP_004 {
    description = "The numeric value validator shall accept a numeric value manager instance as its sole constructor argument"
    safety = ScoreReq.Asil.B
    derived_from = [SampleSEooC.FEAT_003@1, SampleSEooC.FEAT_004@1]
    version = 1
}

ScoreReq.CompReq REQ_COMP_005 {
    description = "The numeric value validator shall take exclusive ownership of the received numeric value manager instance"
    safety = ScoreReq.Asil.B
    derived_from = [SampleSEooC.FEAT_004@1]
    version = 1
}
