/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

package MinimalExample

import ScoreReq

ScoreReq.FeatReq FEAT_001 {
    description  = "The component shall store configuration parameters persistently across restarts"
    safety       = ScoreReq.Asil.B
    derived_from = [MinimalExample.ASR_001@1]
    version      = 1
}

ScoreReq.FeatReq FEAT_002 {
    description  = "The component shall provide read access to all stored configuration parameters"
    safety       = ScoreReq.Asil.B
    derived_from = [MinimalExample.ASR_001@1]
    version      = 1
}
