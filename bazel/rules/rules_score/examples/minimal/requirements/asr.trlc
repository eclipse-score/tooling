/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

package MinimalExample

import ScoreReq

ScoreReq.AssumedSystemReq ASR_001 {
    description = "The system shall support configurable key-value parameters accessible at runtime"
    safety      = ScoreReq.Asil.B
    rationale   = "Runtime configuration is required so the component can be adapted without recompilation"
    version     = 1
}
