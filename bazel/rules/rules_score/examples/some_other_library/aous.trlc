/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package OtherLibrary

import ScoreReq

ScoreReq.AoU TimingConstraint {
    description = "The caller shall ensure that invocations do not exceed 10ms cycle time"
    safety = ScoreReq.Asil.B
    version = 1
}

ScoreReq.AoU SpaceConstraint {
    description = "The caller shall ensure that invocations do not exceed 10 MB"
    safety = ScoreReq.Asil.B
    version = 1
}

ScoreReq.AoU ValidInputPointer {
    description = "The caller shall pass Compute a non-null pointer to a uint8_t object that remains alive and is not modified by any thread until Compute returns"
    safety = ScoreReq.Asil.B
    version = 1
}
