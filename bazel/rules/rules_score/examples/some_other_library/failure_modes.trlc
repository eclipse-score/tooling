/*******************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package OtherLibraryFmea

import ScoreReq
import other_library_api

ScoreReq.FailureMode ComputeOverloaded {
    guidewords = [ScoreReq.Guideword.TooLate]
    description = "Compute is invoked beyond the supported load"
    failureeffect = "Results are delivered late or not at all"
    version = 1
    safety = ScoreReq.Asil.B
    interface = [other_library_api.other_seooc_OtherLibraryAPI_Compute]
}

ScoreReq.FailureMode InvalidInputRead {
    guidewords = [ScoreReq.Guideword.Wrong]
    description = "Compute reads through an invalid or concurrently modified input pointer"
    failureeffect = "The caller receives an incorrect value or execution fails"
    version = 1
    safety = ScoreReq.Asil.B
    interface = [other_library_api.other_seooc_OtherLibraryAPI_Compute]
}
