/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Integrator

import ScoreReq

///////////////////////////////
// Assumed System Requirements
// System level requirements for the integrator
///////////////////////////////

ScoreReq.AssumedSystemReq ASR_INT_001 {
    description = "The system shall integrate the numeric value management SEooC and invoke its interfaces within real-time constraints"
    safety = ScoreReq.Asil.B
    version = 1
    rationale = "System-level requirement for integrating a safety-qualified SEooC into the target platform"
}

ScoreReq.AssumedSystemReq ASR_INT_002 {
    description = "The system shall detect and react to faults reported by integrated SEooC components within a bounded time"
    safety = ScoreReq.Asil.B
    version = 1
    rationale = "System-level requirement for fault handling in a safety-critical integration context"
}
