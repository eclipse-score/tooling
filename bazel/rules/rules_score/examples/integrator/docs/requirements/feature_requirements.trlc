/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Integrator

import ScoreReq

///////////////////////////////
// Feature Requirements
// Requirements for the system integrator that incorporates safety_software_seooc
///////////////////////////////

ScoreReq.FeatReq FEAT_INT_001 {
    description = "The integrator shall initialize the numeric value manager provided by the SEooC within the system startup sequence"
    safety = ScoreReq.Asil.B
    derived_from = [Integrator.ASR_INT_001@1]
    version = 1
}

ScoreReq.FeatReq FEAT_INT_002 {
    description = "The integrator shall invoke the validation interface cyclically with a period no greater than 10ms to ensure timely fault detection"
    safety = ScoreReq.Asil.B
    derived_from = [Integrator.ASR_INT_001@1]
    version = 1
}

ScoreReq.FeatReq FEAT_INT_003 {
    description = "The integrator shall transition to a safe state within 50ms if the validation interface returns a failure result"
    safety = ScoreReq.Asil.B
    derived_from = [Integrator.ASR_INT_002@1]
    version = 1
}

ScoreReq.FeatReq FEAT_INT_004 {
    description = "The integrator shall provide a diagnostic reporting interface that exposes the current health status of all managed SEooC components"
    safety = ScoreReq.Asil.B
    derived_from = [Integrator.ASR_INT_002@1]
    version = 1
}
