/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package UseCases
import ToolQualification
import Tools

section "Use Cases" {

    ToolQualification.UseCase Build_Traceable_Documentation {
        description = '''
            As a safety engineer I want to build HTML documentation from
            requirements, architecture diagrams, and safety analyses so that
            all artefacts are rendered in a single navigable document with
            cross-references and traceability information.
        '''
        affected_tools = [Tools.Bazel, Tools.TRLC, Tools.Docs]
    }

    ToolQualification.UseCase Validate_Requirement_Chains {
        description = '''
            As a requirements engineer I want the build system to validate
            that all component requirements trace back to feature requirements
            and all feature requirements trace back to assumed system
            requirements so that incomplete traceability is detected early.
        '''
        affected_tools = [Tools.TRLC, Tools.Bazel, Tools.Lobster]
    }

    ToolQualification.UseCase Render_Safety_Analyses {
        description = '''
            As a safety engineer I want FMEA failure modes and control
            measures to be rendered into the documentation automatically so
            that the safety analysis artefacts are always up to date with the
            source TRLC definitions.
        '''
        affected_tools = [Tools.TRLC, Tools.Bazel, Tools.Docs]
    }

    ToolQualification.UseCase Assemble_Dependable_Element {
        description = '''
            As a project lead I want to assemble a dependable element (SEooC)
            from its components, requirements, architectural design and safety
            analyses so that the complete safety case is represented as a
            single auditable artefact.
        '''
        affected_tools = [Tools.Bazel]
    }

    ToolQualification.UseCase Identify_Report_Tooling_Version {
        description = '''
            As a safety assessor I want every dependable element report to
            state the tooling version it was generated with so that the report
            can be attributed to a released and qualified tooling version.
        '''
        affected_tools = [Tools.Bazel, Tools.Docs]
    }

    ToolQualification.UseCase Parse_Architectural_Diagrams {
        description = '''
            As a software architect I want PlantUML component and sequence
            diagrams to be parsed and verified during the build so that
            architectural design errors are caught before integration.
        '''
        affected_tools = [Tools.PlantumlParser, Tools.Bazel]
    }

    ToolQualification.UseCase Verify_Architecture_Conformance {
        description = '''
            As a software architect I want the implemented component and unit
            structure to be checked against the static architecture diagrams
            during the build so that the delivered code does not drift away
            from the documented architecture.
        '''
        affected_tools = [Tools.Verifier, Tools.PlantumlParser, Tools.Bazel]
    }

    ToolQualification.UseCase Gate_Traceability_At_Test_Time {
        description = '''
            As a safety engineer I want a test that fails when the traceability
            chain of a dependable element is incomplete so that an element with
            unsatisfied traceability links cannot be released.
        '''
        affected_tools = [Tools.Lobster, Tools.Bazel]
    }

    ToolQualification.UseCase Trace_Failure_Modes_To_Interfaces {
        description = '''
            As a safety engineer I want failure modes to be traceable to the
            public interface elements of the architecture so that every failure
            mode is allocated to a concrete part of the design.
        '''
        affected_tools = [Tools.PlantumlParser, Tools.Lobster, Tools.Bazel]
    }

    ToolQualification.UseCase Aggregate_Safety_Analysis_Report {
        description = '''
            As a safety engineer I want failure modes, control measures and
            fault-tree root causes to be aggregated into a single traceability
            report so that the completeness of the safety analysis can be
            assessed in one place.
        '''
        affected_tools = [Tools.Lobster, Tools.TRLC, Tools.Bazel]
    }

    ToolQualification.UseCase Enforce_Certified_Scope_And_Integrity {
        description = '''
            As a project lead I want the build to fail when a dependable element
            pulls in implementation targets outside its certified scope or
            depends on an element of lower integrity level so that certification
            boundaries are enforced automatically.
        '''
        affected_tools = [Tools.Bazel]
    }

    ToolQualification.UseCase Author_Requirements_In_Rst_Or_Trlc {
        description = '''
            As a requirements engineer I want to author requirements either as
            RST directives or as TRLC records so that existing RST requirement
            sources can be integrated into the traceability chain without manual
            rewriting.
        '''
        affected_tools = [Tools.TRLC, Tools.Bazel]
    }

    ToolQualification.UseCase Verify_Unit_Tests_Pass {
        description = '''
            As a software developer I want unit test results to be captured and
            fed into the traceability report so that requirements are only
            considered verified when their tests actually pass.
        '''
        affected_tools = [Tools.Lobster, Tools.Bazel]
    }

    ToolQualification.UseCase Merge_Cross_Module_Documentation {
        description = '''
            As a documentation author I want the HTML documentation of dependent
            modules to be merged into a single navigable site with working
            cross-references so that a dependable element and its sub-elements
            are read as one document.
        '''
        affected_tools = [Tools.Docs, Tools.Bazel]
    }

    ToolQualification.UseCase Forward_AoU_To_Dependees {
        description = '''
            As a system integrator I want assumptions of use defined by a
            dependable element to be automatically forwarded to the elements
            that depend on it so that the integrating project is made aware
            of all conditions it must satisfy — including those originating
            from transitive dependencies.
        '''
        affected_tools = [Tools.Bazel, Tools.Lobster]
    }

    ToolQualification.UseCase Validate_Architecture_Specification_Documents {
        description = '''
            As a software architect I want the build to verify that architectural
            specification documents (component and sequence diagrams) are consistent
            with the implemented Bazel structure so that specification drift is
            detected automatically during the build.
        '''
        affected_tools = [Tools.Verifier, Tools.PlantumlParser, Tools.Bazel]
    }

    ToolQualification.UseCase Validate_Unit_Specification_Documents {
        description = '''
            As a software developer I want the build to verify that unit design
            class and sequence diagrams are consistent with the corresponding
            implementation artefacts so that unit-level design drift is
            detected automatically during the build.
        '''
        affected_tools = [Tools.Verifier, Tools.PlantumlParser, Tools.LibClang, Tools.Bazel]
    }

    ToolQualification.UseCase Declare_Complete_Coverage {
        description = '''
            As a safety engineer I want to declare that a set of requirements
            is completely covered by automated test cases so that the coverage
            claim is explicit, auditable, and version-controlled.
        '''
        affected_tools = [Tools.TestCaseCoverage]
    }

    ToolQualification.UseCase Detect_Specification_Drift {
        description = '''
            In the CI pipeline I want to detect automatically when a test's
            given/when/then specification or formal test specification has
            changed without re-approval so that stale coverage claims are
            caught before release.
        '''
        affected_tools = [Tools.TestCaseCoverage]
    }

    ToolQualification.UseCase Formal_Test_Specification {
        description = '''
            As a test engineer I want to specify a complex test case in a
            formal test specification document (test goal, test focus, test
            steps) instead of a given/when/then description, so that
            multi-step and higher-order tests are specified completely and
            the specification is part of the reviewed coverage claim.
        '''
        affected_tools = [Tools.TestCaseCoverage, Tools.Bazel]
    }

    ToolQualification.UseCase Detect_Coverage_Set_Changes {
        description = '''
            In the CI pipeline I want to detect when a test case is added to or
            removed from the set of tests linked to a requirement so that
            undeclared coverage changes cannot pass silently.
        '''
        affected_tools = [Tools.TestCaseCoverage]
    }

    ToolQualification.UseCase Generate_Covered_Traceability_Artifact {
        description = '''
            As a project integrator I want the tool to emit a LOBSTER-compatible
            artifact that marks each linked test case as covered or not so that
            complete requirement coverage is visible in the LOBSTER dashboard.
        '''
        affected_tools = [Tools.TestCaseCoverage, Tools.Lobster]
    }

    ToolQualification.UseCase Semi_Automated_Lock_Update {
        description = '''
            As an engineer I want a single bazel run command that reads
            requirement identifiers from the TRLC requirements target,
            discovers all linked test cases in the GTest XML results, and
            rewrites the lock file, so that I only need to review the diff
            before committing my approval.
        '''
        affected_tools = [Tools.TestCaseCoverage, Tools.Bazel]
    }

    ToolQualification.UseCase Perform_Manual_Analysis {
        description = '''
            As a reviewer I want to follow a defined manual analysis procedure
            and retain my answers, command outcomes and final assertion so
            that the review evidence is auditable and incomplete or negative
            analyses are rejected by the verification test.
        '''
        affected_tools = [Tools.ManualAnalysis, Tools.Bazel]
    }

    ToolQualification.UseCase Detect_Stale_Manual_Analysis {
        description = '''
            As a safety engineer I want verification to detect changes to the
            reviewed context, procedure, results or relevant build configuration
            so that outdated manual analysis evidence cannot pass unnoticed.
        '''
        affected_tools = [Tools.ManualAnalysis, Tools.Bazel]
    }

    ToolQualification.UseCase Trace_Manual_Analysis_Evidence {
        description = '''
            As a project integrator I want manual analysis evidence and its
            verification outcome to be exported with links to the reviewed
            requirements so that traceability tooling can consume both passing
            and failing outcomes without confusing traceability completeness
            with verification success.
        '''
        affected_tools = [Tools.ManualAnalysis, Tools.Lobster, Tools.Bazel]
    }
}
