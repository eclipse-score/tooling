/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package UseCases
import ToolQualification
import Tools

section "Tool Requirements" {

    section "Requirements Rendering" {

        ToolQualification.ToolRequirement Render_All_TRLC_Records {
            description = '''
                The trlc_rst renderer shall produce an RST output that contains
                every requirement record present in the input TRLC source files.
            '''
            mitigates = [Missing_Requirement_In_Output]
            derived_from = [Build_Traceable_Documentation]
            satisfied_by = Tools.TRLC
        }

        ToolQualification.ToolRequirement Resolve_Derived_From_References {
            description = '''
                The rendered RST output shall contain working cross-references
                for all derived_from fields, linking child requirements to their
                parent requirements.
            '''
            mitigates = [Broken_Cross_Reference]
            derived_from = [Build_Traceable_Documentation]
            satisfied_by = Tools.TRLC
        }

    }

    section "Requirement Validation" {

        ToolQualification.ToolRequirement Validate_Traceability_Completeness {
            description = '''
                The build shall fail when a component requirement does not have
                a derived_from reference to at least one feature requirement,
                unless the requirement is explicitly marked as component-internal.
            '''
            mitigates = [Undetected_Missing_Traceability]
            derived_from = [Validate_Requirement_Chains]
            satisfied_by = Tools.Bazel
        }

        ToolQualification.ToolRequirement Emit_Correct_Provider_Info {
            description = '''
                The score_requirements_rule shall emit a TrlcProviderInfo
                provider containing all own TRLC source files, the specification
                RSL files, and all transitive dependency TRLC files.
            '''
            mitigates = [Incorrect_Provider_Chain]
            derived_from = [Validate_Requirement_Chains]
            satisfied_by = Tools.Bazel
        }

        ToolQualification.ToolRequirement Emit_Sphinx_Sources {
            description = '''
                The score_requirements_rule shall emit a SphinxSourcesInfo
                provider containing the rendered RST file and all transitive
                Sphinx source dependencies.
            '''
            mitigates = [Incorrect_Provider_Chain]
            derived_from = [Build_Traceable_Documentation]
            satisfied_by = Tools.Bazel
        }

    }

    section "Safety Analysis Rendering" {

        ToolQualification.ToolRequirement Render_All_Failure_Modes {
            description = '''
                The safety_analysis rule shall render every FailureMode record of
                its failure_modes into the documentation output.
            '''
            mitigates = [Missing_Failure_Mode_In_Render]
            derived_from = [Render_Safety_Analyses]
            satisfied_by = Tools.Docs
        }

    }

    section "Root Cause Assessment" {

        ToolQualification.ToolRequirement Render_Root_Cause_Assessments {
            description = '''
                The safety_analysis rule shall render, for every root cause
                of its fault_trees, the ASIL, the rationale and the measures
                (name, kind and version) of the RootCauseAssessment that
                lists the root cause. It shall mark a root cause that no
                assessment lists as "Not assessed", and a root cause whose
                assessment has no measure as "Not applicable".
            '''
            mitigates = [Unassessed_Root_Cause_Accepted]
            derived_from = [Render_Safety_Analyses]
            satisfied_by = Tools.Docs
        }

        ToolQualification.ToolRequirement Reject_Inconsistent_Assessment_Asil {
            description = '''
                The safety_analysis rule shall fail the build when the ASIL
                of a RootCauseAssessment is lower than the ASIL of a failure
                mode of one of its root causes, or higher than the ASIL of
                one of its measures, and the error message shall name the
                assessment and the failure mode or measure.
            '''
            mitigates = [Underrated_Root_Cause_Assessment]
            derived_from = [Aggregate_Safety_Analysis_Report]
            satisfied_by = Tools.Bazel
        }

        ToolQualification.ToolRequirement Reject_Root_Cause_In_Multiple_Assessments {
            description = '''
                The safety_analysis rule shall fail the build when more than
                one RootCauseAssessment lists the same root cause, and the
                error message shall name the root cause and every assessment
                that lists it.
            '''
            mitigates = [Ambiguous_Root_Cause_Assessment]
            derived_from = [Aggregate_Safety_Analysis_Report]
            satisfied_by = Tools.Bazel
        }

        ToolQualification.ToolRequirement Reject_Foreign_Assessment_References {
            description = '''
                The safety_analysis rule shall fail the build when a
                RootCauseAssessment lists a root cause that its fault_trees
                target does not generate, or a measure that is not an own
                record of a target in its safety_measures, and the error
                message shall name the assessment and the reference.
            '''
            mitigates = [Ambiguous_Root_Cause_Assessment]
            derived_from = [Aggregate_Safety_Analysis_Report]
            satisfied_by = Tools.Bazel
        }

        ToolQualification.ToolRequirement Reject_Non_Assessment_Records {
            description = '''
                The safety_analysis rule shall fail the build when a file
                passed as assessments contains a record that is not a
                RootCauseAssessment, and the error message shall name the
                record.
            '''
            mitigates = [Ambiguous_Root_Cause_Assessment]
            derived_from = [Aggregate_Safety_Analysis_Report]
            satisfied_by = Tools.Bazel
        }

        ToolQualification.ToolRequirement Cover_Root_Causes_And_AoUs_By_Assessment {
            description = '''
                The lobster traceability report of a dependable element shall
                require every root cause to be listed by a
                RootCauseAssessment, and every own assumption of use to be
                listed as a measure of one, so that the existing
                lobster-ci-report test fails otherwise.
            '''
            mitigates = [Unassessed_Root_Cause_Accepted]
            derived_from = [Aggregate_Safety_Analysis_Report, Gate_Traceability_At_Test_Time]
            satisfied_by = Tools.Lobster
        }

        ToolQualification.ToolRequirement Pin_Assessed_Measure_Version {
            description = '''
                A RootCauseAssessment shall reference each of its measures
                with the version of the measure, and the lobster
                traceability report shall flag the reference as unresolved
                when the measure has another version.
            '''
            mitigates = [Stale_Root_Cause_Assessment]
            derived_from = [Aggregate_Safety_Analysis_Report]
            satisfied_by = Tools.Lobster
        }

    }

    section "Report Provenance" {

        ToolQualification.ToolRequirement Report_Tooling_Version {
            description = '''
                The dependable_element rule shall state the resolved
                score_tooling module version on the landing page of the
                generated documentation without requiring configuration by the
                consuming module. When the resolved module has no version, the
                page shall state that the version is unavailable.
            '''
            mitigates = [Wrong_Tooling_Version_In_Report]
            note = "Versions are only available for score_tooling releases consumed through a Bazel registry."
            derived_from = [Identify_Report_Tooling_Version]
            satisfied_by = Tools.Bazel
        }

    }

    section "Architecture Parsing" {

        ToolQualification.ToolRequirement Reject_Invalid_PlantUML {
            description = '''
                The PlantUML parser shall exit with a non-zero return code when
                the input diagram contains syntactical errors, preventing silent
                production of incorrect output.
            '''
            mitigates = [Silent_Diagram_Parse_Failure]
            note = "This requirement traces to the plantuml parser source (Rust)."
            derived_from = [Parse_Architectural_Diagrams]
            satisfied_by = Tools.PlantumlParser
        }

    }

    section "Lobster Traceability" {

        ToolQualification.ToolRequirement Extract_Lobster_From_Requirements {
            description = '''
                The requirements rule shall extract a lobster traceability file
                from all TRLC requirement records using the configured lobster
                extraction schema.
            '''
            mitigates = [Undetected_Missing_Traceability]
            derived_from = [Validate_Requirement_Chains]
            satisfied_by = Tools.Lobster
        }

    }

    section "AoU Forwarding" {

        ToolQualification.ToolRequirement Forward_Own_AoUs_To_Dependees {
            description = '''
                The dependable_element rule shall automatically include lobster
                traceability entries for all assumptions of use defined by its
                direct dependencies in the dependee's traceability report as
                a "Received AoUs" tier.
            '''
            mitigates = [AoU_Silently_Dropped]
            derived_from = [Forward_AoU_To_Dependees]
            satisfied_by = Tools.Bazel
        }

        ToolQualification.ToolRequirement Chain_Forward_Received_AoUs {
            description = '''
                The dependable_element rule shall support an aou_forwarding
                attribute pointing to a YAML file that selects which received
                AoUs are forwarded further to elements that depend on this
                element. Each entry in the YAML shall require a mandatory
                justification field and the version of the AoU it forwards,
                so that a justification is reviewed again when the AoU
                changes.
            '''
            mitigates = [AoU_Silently_Dropped]
            derived_from = [Forward_AoU_To_Dependees]
            satisfied_by = Tools.Bazel
        }

        ToolQualification.ToolRequirement Reject_Unknown_AoU_In_Forwarding_YAML {
            description = '''
                The AoU forwarding tool shall exit with a non-zero return code
                when the forwarding YAML references an AoU identifier, or an
                AoU version, that does not exist in the set of received AoUs,
                or lists an AoU identifier more than once, preventing silent
                misconfiguration.
            '''
            mitigates = [Invalid_Forwarding_YAML_Accepted]
            derived_from = [Forward_AoU_To_Dependees]
            satisfied_by = Tools.Bazel
        }

        ToolQualification.ToolRequirement Derive_Own_AoUs_From_Safety_Analysis {
            description = '''
                The dependable_element rule shall derive the assumptions of
                use it exposes to its dependees from the assumptions_of_use
                targets that the safety_analysis targets of its
                dependability_analysis consume as safety_measures, and shall provide
                no other source of own assumptions of use. An assumption of
                use shall be exposed once, however many safety analyses
                consume it.
            '''
            mitigates = [AoU_Silently_Dropped]
            derived_from = [Forward_AoU_To_Dependees]
            satisfied_by = Tools.Bazel
        }

        ToolQualification.ToolRequirement Receive_Duplicate_AoU_Once {
            description = '''
                The dependable_element rule shall list an assumption of use in
                its "Received AoUs" tier once, when it reaches the element
                along several paths with identical content, such as through a
                direct dependency and through a dependency that forwards it.
            '''
            derived_from = [Forward_AoU_To_Dependees]
            satisfied_by = Tools.Bazel
        }

        ToolQualification.ToolRequirement Reject_Conflicting_AoU_Definitions {
            description = '''
                The dependable_element rule shall fail the build when an
                assumption of use reaches the element along several paths
                with different content, such as in different versions, and
                the error message shall name the assumption of use and the
                differing fields.
            '''
            mitigates = [Conflicting_AoU_Definitions_Merged]
            derived_from = [Forward_AoU_To_Dependees]
            satisfied_by = Tools.Bazel
        }

        ToolQualification.ToolRequirement Cover_Received_AoU_Via_Manual_Analysis {
            description = '''
            The dependable_element rule shall include manual analysis
            evidence referencing received AoU records directly in its
            "Received AoUs" coverage policy.
            '''
            mitigates = [AoU_Silently_Dropped]
            derived_from = [Forward_AoU_To_Dependees, Gate_Traceability_At_Test_Time]
            satisfied_by = Tools.Lobster
        }

        ToolQualification.ToolRequirement Include_Forwarded_AoUs_In_Traceability {
            description = '''
                The lobster traceability report of a dependable element shall
                require every item in its "Received AoUs" tier to be covered
                by at least one of: manual analysis (via a direct reference)
                or a chain-forwarding entry (via
                aou_forwarding), so that the existing lobster-ci-report test
                fails when a received AoU is neither handled nor forwarded.
            '''
            mitigates = [AoU_Silently_Dropped]
            derived_from = [Forward_AoU_To_Dependees, Gate_Traceability_At_Test_Time]
            satisfied_by = Tools.Lobster
        }

    }

    section "Test Case Coverage" {

        ToolQualification.ToolRequirement Lock_File_As_Spec_And_Approval {
            description = '''
                The tool shall use one YAML lock file as both the declaration of
                which requirements are claimed to be completely covered and as the
                committed approval artifact.
            '''
            derived_from = [Declare_Complete_Coverage]
            satisfied_by = Tools.TestCaseCoverage
        }

        ToolQualification.ToolRequirement Requirement_IDs_From_TRLC {
            description = '''
                The tool shall extract requirement identifiers automatically from
                the TrlcProviderInfo provider of the requirements target attribute.
            '''
            derived_from = [Semi_Automated_Lock_Update, Declare_Complete_Coverage]
            satisfied_by = Tools.TestCaseCoverage
        }

        ToolQualification.ToolRequirement Parse_GWT_Annotations {
            description = '''
                The tool shall read the requirement references, the given,
                when, and then parts, and the test-spec reference of every test
                case from the gtest.lobster file that lobster-gtest produces
                from the GTest XML result files. A test case without a given,
                when, or then part shall be included with an empty string for
                each missing part.
            '''
            derived_from = [Detect_Specification_Drift, Detect_Coverage_Set_Changes]
            satisfied_by = Tools.TestCaseCoverage
        }

        ToolQualification.ToolRequirement Validate_Test_Specification {
            description = '''
                The test_specification rule shall fail the build for an RST
                file that does not consist of exactly one title section with
                a non-empty Test Goal section, an optional Test Focus section,
                and a Test Steps section with at least one step subsection.
                Each step shall consist of one field list with an optional
                Precondition and a non-empty Action and Expected field. Any
                other section, field, or text, and any RST warning or error,
                shall fail the build, independent of the maturity.
            '''
            derived_from = [Formal_Test_Specification]
            satisfied_by = Tools.TestCaseCoverage
        }

        ToolQualification.ToolRequirement Resolve_Test_Specification {
            description = '''
                For a test case with a test-spec reference, the tool shall
                look up the test_specification among the test_specs of the
                component's units by the label as written in the unit's
                test_specs, independent of canonical repository names. It
                shall use its test goal, test focus, and test steps instead of
                the given, when, and then parts, which shall be ignored with a
                warning. A reference that matches different test
                specifications shall not resolve.
            '''
            derived_from = [Formal_Test_Specification, Detect_Specification_Drift]
            satisfied_by = Tools.TestCaseCoverage
        }

        ToolQualification.ToolRequirement Enable_GWT_Derivation {
            description = '''
                The component rule shall pass the option
                --derive-gwt-from-test-name to lobster-gtest when the resolved
                lobster version provides that option, and shall omit it
                otherwise.
            '''
            derived_from = [Detect_Specification_Drift]
            satisfied_by = Tools.Bazel
        }

        ToolQualification.ToolRequirement Derive_GWT_From_Test_Name {
            description = '''
                With the option --derive-gwt-from-test-name, lobster-gtest
                shall derive the given, when, and then parts of a test case
                from its test name, if the name matches
                [<Prefix>_]Given<X>[_When<Y>]_(Expect|Then)<Z>. <Prefix> is
                alphanumeric, and <X>, <Y>, and <Z> are in CamelCase. Each
                derived part is its CamelCase text converted to lowercase
                words separated by spaces. A test case whose name has no When
                part shall have an empty when field. A test case that sets a
                non-blank given, when, or then RecordProperty shall take all
                three parts from its RecordProperty values only, and its
                name shall be ignored.
            '''
            derived_from = [Detect_Specification_Drift]
            satisfied_by = Tools.Lobster
        }

        ToolQualification.ToolRequirement Require_Given_And_Then {
            description = '''
                The tool shall report every linked test case without a
                test-spec reference whose given or then field is empty or
                blank as an error naming the requirement identifier, the test
                uid, and the missing fields. An empty when field shall not be
                reported. A test-spec reference that does not resolve to a
                test_specification shall be reported as an error naming the
                requirement identifier, the test uid, and the reference. The error shall fail the
                test action, and shall prevent the .update command from
                writing the lock file, unless check failures are allowed.
            '''
            derived_from = [Declare_Complete_Coverage, Detect_Specification_Drift]
            satisfied_by = Tools.TestCaseCoverage
        }

        ToolQualification.ToolRequirement Multi_Requirement_Linking {
            description = '''
                A test case that carries lobster-tracing values matching more than
                one requirement identifier shall appear in the lock file entry of
                every matched requirement.
            '''
            derived_from = [Declare_Complete_Coverage]
            satisfied_by = Tools.TestCaseCoverage
        }

        ToolQualification.ToolRequirement Lock_File_Content {
            description = '''
                The lock file shall contain, per requirement: the requirement
                identifier and an ordered list of linked test cases. Each test
                case entry shall contain: a uid in the format
                "//bazel_package/SuiteName:TestName" (package-scoped gtest tag)
                and either the individual given, when, and then strings as
                separate fields, or, for a test case with a test
                specification, a spec field holding the label, test goal, test
                focus, and test steps (precondition, action, expected) of the
                test specification. An entry with both shall be rejected.
            '''
            derived_from = [Detect_Specification_Drift, Declare_Complete_Coverage]
            satisfied_by = Tools.TestCaseCoverage
        }

        ToolQualification.ToolRequirement Lock_File_Ordering {
            description = '''
                Test cases within a requirement entry shall be ordered
                lexicographically by uid to produce a deterministic,
                diff-friendly lock file.
            '''
            derived_from = [Detect_Specification_Drift, Detect_Coverage_Set_Changes]
            satisfied_by = Tools.TestCaseCoverage
        }

        ToolQualification.ToolRequirement Update_Command {
            description = '''
                The .update Bazel run target shall extract requirement identifiers
                from the TrlcProviderInfo target, parse GTest XML result files for
                lobster-tracing-linked test cases, build the spec from
                given/when/then or the referenced test specification, and
                overwrite the committed lock file.
            '''
            derived_from = [Semi_Automated_Lock_Update]
            satisfied_by = Tools.TestCaseCoverage
        }

        ToolQualification.ToolRequirement Test_Command_Verification {
            description = '''
                The Bazel test target shall parse GTest XML result files, rebuild
                the spec for each linked test, and compare uid and spec against
                the committed lock file, failing if they differ. On failure it
                shall print a human-readable diff showing which test cases changed
                and the exact bazel run command needed to refresh the lock file.
            '''
            derived_from = [Detect_Specification_Drift, Detect_Coverage_Set_Changes]
            satisfied_by = Tools.TestCaseCoverage
        }

        ToolQualification.ToolRequirement LOBSTER_Covered_Attribute {
            description = '''
                The test target shall emit a lobster-act-trace JSON artifact that
                marks each linked test case as "ok" when its uid exists in the
                committed lock file and its spec matches, and "fail" otherwise.
            '''
            derived_from = [Generate_Covered_Traceability_Artifact]
            satisfied_by = Tools.TestCaseCoverage
        }

    }

}
