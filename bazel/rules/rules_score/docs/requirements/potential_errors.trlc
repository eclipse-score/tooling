/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package rules_score
import ToolQualification

section "Potential Errors" {

    section "Documentation Build" {

        ToolQualification.PotentialError Missing_Requirement_In_Output {
            description = '''
                A requirement defined in a TRLC source file is silently omitted
                from the rendered RST output, causing the documentation to be
                incomplete without any build error.
            '''
            impacts = ["Incomplete safety documentation delivered to assessor"]
            affects = [Build_Traceable_Documentation]
            impact_type = ToolQualification.Impact_Type.Safety
        }

        ToolQualification.PotentialError Broken_Cross_Reference {
            description = '''
                A cross-reference between requirements (e.g. derived_from) is
                not resolved correctly in the rendered documentation, showing
                a broken link or missing reference.
            '''
            impacts = ["Traceability information is incorrect in delivered documentation"]
            affects = [Build_Traceable_Documentation, Validate_Requirement_Chains]
            impact_type = ToolQualification.Impact_Type.Safety
        }

        ToolQualification.PotentialError Wrong_Tooling_Version_In_Report {
            description = '''
                The dependable element report states no tooling version, or a
                version other than the resolved score_tooling module version,
                such as the version of the consuming module.
            '''
            impacts = ["Report cannot be attributed to the tooling version that generated it"]
            affects = [Identify_Report_Tooling_Version]
            impact_type = ToolQualification.Impact_Type.Safety
        }

    }

    section "Requirement Traceability" {

        ToolQualification.PotentialError Undetected_Missing_Traceability {
            description = '''
                A component requirement that lacks a derived_from reference to
                a feature requirement is not flagged as an error during the
                build, allowing gaps in the traceability chain.
            '''
            impacts = ["Safety requirements may not be implemented"]
            affects = [Validate_Requirement_Chains]
            impact_type = ToolQualification.Impact_Type.Safety
        }

        ToolQualification.PotentialError Incorrect_Provider_Chain {
            description = '''
                The Bazel provider chain (TrlcProviderInfo, SphinxSourcesInfo)
                is assembled incorrectly so that downstream rules receive stale
                or incomplete requirement data.
            '''
            impacts = ["Traceability report based on outdated information"]
            affects = [Validate_Requirement_Chains, Assemble_Dependable_Element]
            impact_type = ToolQualification.Impact_Type.Safety
        }

    }

    section "Safety Analysis" {

        ToolQualification.PotentialError Missing_Failure_Mode_In_Render {
            description = '''
                A failure mode defined in TRLC is not rendered in the FMEA
                documentation output, causing an incomplete safety analysis
                artefact.
            '''
            impacts = ["Incomplete FMEA delivered as part of safety case"]
            affects = [Render_Safety_Analyses, Assemble_Dependable_Element]
            impact_type = ToolQualification.Impact_Type.Safety
        }

        ToolQualification.PotentialError Unassessed_Root_Cause_Accepted {
            description = '''
                A fault-tree root cause that no root cause assessment lists,
                or an own assumption of use that no assessment uses, passes
                the build, and the documentation shows no gap.
            '''
            impacts = ["Root cause without a safety argument delivered as part of the safety case"]
            affects = [Render_Safety_Analyses, Aggregate_Safety_Analysis_Report]
            impact_type = ToolQualification.Impact_Type.Safety
        }

        ToolQualification.PotentialError Ambiguous_Root_Cause_Assessment {
            description = '''
                A root cause is listed by several root cause assessments, or
                an assessment lists a root cause or measure that does not
                belong to its safety analysis, so the rendered argument does
                not match the analysed fault trees and measures.
            '''
            impacts = ["Contradicting or foreign safety arguments in the delivered safety case"]
            affects = [Render_Safety_Analyses, Aggregate_Safety_Analysis_Report]
            impact_type = ToolQualification.Impact_Type.Safety
        }

        ToolQualification.PotentialError Stale_Root_Cause_Assessment {
            description = '''
                A measure changes, but the root cause assessment that
                relies on its earlier version is not reviewed again.
            '''
            impacts = ["Safety argument based on an outdated measure"]
            affects = [Aggregate_Safety_Analysis_Report]
            impact_type = ToolQualification.Impact_Type.Safety
        }

        ToolQualification.PotentialError Underrated_Root_Cause_Assessment {
            description = '''
                A root cause of a failure mode is assessed with a lower
                ASIL than the failure mode, or a root cause assessment
                relies on a measure of a lower ASIL than its own, and the
                build passes.
            '''
            impacts = ["Root cause of a high-ASIL failure mode closed by an argument or measure of a lower ASIL in the safety case"]
            affects = [Render_Safety_Analyses, Aggregate_Safety_Analysis_Report]
            impact_type = ToolQualification.Impact_Type.Safety
        }

    }

    section "Architecture" {

        ToolQualification.PotentialError Silent_Diagram_Parse_Failure {
            description = '''
                A syntactically invalid PlantUML diagram is not rejected by
                the parser, producing an incorrect or empty FlatBuffers output
                that is consumed silently by downstream rules.
            '''
            impacts = ["Architecture verification based on incorrect model"]
            affects = [Parse_Architectural_Diagrams, Assemble_Dependable_Element]
            impact_type = ToolQualification.Impact_Type.Safety
        }

    }

    section "AoU Forwarding" {

        ToolQualification.PotentialError AoU_Silently_Dropped {
            description = '''
                An assumption of use defined by a dependency is not forwarded
                to the dependee, causing the integrating project to be unaware
                of a condition it must satisfy.
            '''
            impacts = ["Safety-relevant assumption not communicated to integrator"]
            affects = [Forward_AoU_To_Dependees, Gate_Traceability_At_Test_Time]
            impact_type = ToolQualification.Impact_Type.Safety
        }

        ToolQualification.PotentialError Invalid_Forwarding_YAML_Accepted {
            description = '''
                A chain-forwarding YAML file that references a non-existent
                AoU identifier is accepted without error, causing the build to
                succeed while the intended forwarding does not take effect.
            '''
            impacts = ["Chain-forwarded AoU missing from traceability report"]
            affects = [Forward_AoU_To_Dependees]
            impact_type = ToolQualification.Impact_Type.Safety
        }

        ToolQualification.PotentialError Conflicting_AoU_Definitions_Merged {
            description = '''
                An assumption of use reaches a dependable element along
                several paths with different content, for example in two
                versions, and one definition silently replaces the other.
            '''
            impacts = ["Integrator is shown an outdated or wrong assumption of use"]
            affects = [Forward_AoU_To_Dependees]
            impact_type = ToolQualification.Impact_Type.Safety
        }

    }

}
