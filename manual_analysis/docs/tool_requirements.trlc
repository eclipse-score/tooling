/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package ManualAnalysisRequirements
import ToolQualification
import Tools
import UseCases

section "Tool Requirements" {

    section "Manual Analysis" {

        section "Target Structure" {

            ToolQualification.ToolRequirement ManualAnalysisUpdateTargetName {
                derived_from = [UseCases.Perform_Manual_Analysis]
                satisfied_by = Tools.ManualAnalysis
                description = '''The `manual_analysis` macro shall define a Bazel target named `<name>.update` that is invocable via `bazel run`, where `<name>` is the `name` attribute of the macro invocation.'''
            }

            ToolQualification.ToolRequirement ManualAnalysisTestTargetName {
                derived_from = [UseCases.Perform_Manual_Analysis]
                satisfied_by = Tools.ManualAnalysis
                description = '''The `manual_analysis` macro shall define a Bazel target named `<name>` that is invocable via `bazel test`, where `<name>` is the `name` attribute of the macro invocation.'''
            }

            ToolQualification.ToolRequirement ManualAnalysisContextProviderContract {
                derived_from = [UseCases.Detect_Stale_Manual_Analysis]
                satisfied_by = Tools.ManualAnalysis
                description = '''The manual-analysis tooling shall reject any `contexts` entry from a target that does not provide `ManualAnalysisContextInfo`, during Bazel analysis.'''
            }

        }

        section "Lock-File Integrity" {

            ToolQualification.ToolRequirement ManualAnalysisLockFileInputCoverage {
                derived_from = [UseCases.Detect_Stale_Manual_Analysis]
                satisfied_by = Tools.ManualAnalysis
                description = '''The manual-analysis tooling shall include a SHA-256 hash of the byte content of each file collected from all provided `ManualAnalysisContextInfo.files` depsets, the analysis YAML file, and the results file when computing the lock file.'''
            }

            ToolQualification.ToolRequirement ManualAnalysisLockRuleInputCoverage {
                derived_from = [UseCases.Detect_Stale_Manual_Analysis]
                satisfied_by = Tools.ManualAnalysis
                description = '''The manual-analysis tooling shall include a SHA-256 hash of each JSON-encoded rule attribute string collected from all provided `ManualAnalysisContextInfo.rules` depsets when computing the lock file.'''
            }

            ToolQualification.ToolRequirement ManualAnalysisLockDeterminism {
                derived_from = [UseCases.Detect_Stale_Manual_Analysis]
                satisfied_by = Tools.ManualAnalysis
                description = '''The manual-analysis tooling shall write lock entries in ascending lexicographic order of their sort key, where the sort key is the workspace-relative path for file entries and the rule label for rule entries.'''
            }

            ToolQualification.ToolRequirement ManualAnalysisLockMismatchDetection {
                derived_from = [UseCases.Detect_Stale_Manual_Analysis]
                satisfied_by = Tools.ManualAnalysis
                description = '''The manual-analysis test target shall fail when the computed lock file content is not byte-identical to the committed lock file content.'''
            }

            ToolQualification.ToolRequirement ManualAnalysisLockFilesExistForVerification {
                derived_from = [UseCases.Detect_Stale_Manual_Analysis]
                satisfied_by = Tools.ManualAnalysis
                description = '''The manual-analysis tooling shall fail lock-file verification when the computed lock file or the committed lock file does not exist.'''
            }

        }

        section "Analysis Schema" {

            ToolQualification.ToolRequirement ManualAnalysisRequirementsFieldPresent {
                derived_from = [UseCases.Trace_Manual_Analysis_Evidence]
                satisfied_by = Tools.ManualAnalysis
                description = '''The manual-analysis tooling shall reject an analysis YAML file when the `requirements` field is missing.'''
            }

            ToolQualification.ToolRequirement ManualAnalysisRequirementsFieldListType {
                derived_from = [UseCases.Trace_Manual_Analysis_Evidence]
                satisfied_by = Tools.ManualAnalysis
                description = '''The manual-analysis tooling shall reject an analysis YAML file when `requirements` is not a list.'''
            }

            ToolQualification.ToolRequirement ManualAnalysisRequirementsFieldNonEmpty {
                derived_from = [UseCases.Trace_Manual_Analysis_Evidence]
                satisfied_by = Tools.ManualAnalysis
                description = '''The manual-analysis tooling shall reject an analysis YAML file when `requirements` is an empty list.'''
            }

            ToolQualification.ToolRequirement ManualAnalysisRequirementIdentifierStringType {
                derived_from = [UseCases.Trace_Manual_Analysis_Evidence]
                satisfied_by = Tools.ManualAnalysis
                description = '''The manual-analysis tooling shall reject an analysis YAML file when any entry in `requirements` is not a string.'''
            }

            ToolQualification.ToolRequirement ManualAnalysisRequirementIdentifierNonEmpty {
                derived_from = [UseCases.Trace_Manual_Analysis_Evidence]
                satisfied_by = Tools.ManualAnalysis
                description = '''The manual-analysis tooling shall reject an analysis YAML file when any string entry in `requirements` is empty after trimming whitespace.'''
            }

            ToolQualification.ToolRequirement ManualAnalysisSupportedStepTypes {
                derived_from = [UseCases.Perform_Manual_Analysis]
                satisfied_by = Tools.ManualAnalysis
                description = '''The manual-analysis tooling shall reject an analysis YAML file when any `steps` entry uses a step type other than `action`, `automated_action`, `decision`, `assertion`, or `repeat`.'''
            }

            ToolQualification.ToolRequirement ManualAnalysisStepsFieldPresent {
                derived_from = [UseCases.Perform_Manual_Analysis]
                satisfied_by = Tools.ManualAnalysis
                description = '''The manual-analysis tooling shall reject an analysis YAML file when the `steps` field is missing.'''
            }

            ToolQualification.ToolRequirement ManualAnalysisStepsFieldListType {
                derived_from = [UseCases.Perform_Manual_Analysis]
                satisfied_by = Tools.ManualAnalysis
                description = '''The manual-analysis tooling shall reject an analysis YAML file when `steps` is not a list.'''
            }

            ToolQualification.ToolRequirement ManualAnalysisStepsNonEmpty {
                derived_from = [UseCases.Perform_Manual_Analysis]
                satisfied_by = Tools.ManualAnalysis
                description = '''The manual-analysis tooling shall reject an analysis YAML file when `steps` is an empty list.'''
            }

            ToolQualification.ToolRequirement ManualAnalysisFinalStepAssertionType {
                derived_from = [UseCases.Perform_Manual_Analysis]
                satisfied_by = Tools.ManualAnalysis
                description = '''The manual-analysis tooling shall reject an analysis YAML file when the last entry in `steps` does not use the `assertion` step type.'''
            }

        }

        section "Execution And Verdict" {

            ToolQualification.ToolRequirement ManualAnalysisUpdateRunsInteractiveFlow {
                derived_from = [UseCases.Perform_Manual_Analysis]
                satisfied_by = Tools.ManualAnalysis
                description = '''The manual-analysis update target shall guide the user through each step defined in the analysis YAML file in sequence.'''
            }

            ToolQualification.ToolRequirement ManualAnalysisUpdateRefreshesLockInSameInvocation {
                derived_from = [UseCases.Detect_Stale_Manual_Analysis]
                satisfied_by = Tools.ManualAnalysis
                description = '''The manual-analysis update target shall recompute and write the lock file after completing the guided step execution, within the same invocation.'''
            }

            ToolQualification.ToolRequirement ManualAnalysisResultsFileWrittenAfterEachStep {
                derived_from = [UseCases.Perform_Manual_Analysis]
                satisfied_by = Tools.ManualAnalysis
                description = '''The manual-analysis update target shall write all step outcomes recorded so far to the results file after each step completes.'''
            }

            ToolQualification.ToolRequirement ManualAnalysisResultsFilePartialRunOnInterrupt {
                derived_from = [UseCases.Perform_Manual_Analysis]
                satisfied_by = Tools.ManualAnalysis
                description = '''The manual-analysis update target shall append a failing assertion entry with `partial_run = true` to the results list and write the results file when the process receives an interrupt signal or the input stream is closed before all steps complete.'''
            }

            ToolQualification.ToolRequirement ManualAnalysisResultsAnalysisPathWritten {
                derived_from = [UseCases.Perform_Manual_Analysis]
                satisfied_by = Tools.ManualAnalysis
                description = '''The manual-analysis update target shall write the top-level `analysis` field in the results file as the workspace-relative path of the analysis YAML file.'''
            }

            ToolQualification.ToolRequirement ManualAnalysisResultsFileExists {
                derived_from = [UseCases.Perform_Manual_Analysis]
                satisfied_by = Tools.ManualAnalysis
                description = '''The manual-analysis tooling shall reject a results file when the results file does not exist.'''
            }

            ToolQualification.ToolRequirement ManualAnalysisResultsFileReadable {
                derived_from = [UseCases.Perform_Manual_Analysis]
                satisfied_by = Tools.ManualAnalysis
                description = '''The manual-analysis tooling shall reject a results file when the results file cannot be read.'''
            }

            ToolQualification.ToolRequirement ManualAnalysisResultsFileValidJson {
                derived_from = [UseCases.Perform_Manual_Analysis]
                satisfied_by = Tools.ManualAnalysis
                description = '''The manual-analysis tooling shall reject a results file when the results file content is not valid JSON.'''
            }

            ToolQualification.ToolRequirement ManualAnalysisResultsPayloadType {
                derived_from = [UseCases.Perform_Manual_Analysis]
                satisfied_by = Tools.ManualAnalysis
                description = '''The manual-analysis tooling shall reject a results file when the top-level JSON value is not an object.'''
            }

            ToolQualification.ToolRequirement ManualAnalysisResultsKeyPresent {
                derived_from = [UseCases.Perform_Manual_Analysis]
                satisfied_by = Tools.ManualAnalysis
                description = '''The manual-analysis tooling shall reject a results file when the `results` key is absent from the top-level JSON object.'''
            }

            ToolQualification.ToolRequirement ManualAnalysisResultsListType {
                derived_from = [UseCases.Perform_Manual_Analysis]
                satisfied_by = Tools.ManualAnalysis
                description = '''The manual-analysis tooling shall reject a results file when `results` is not a list.'''
            }

            ToolQualification.ToolRequirement ManualAnalysisResultsListNonEmpty {
                derived_from = [UseCases.Perform_Manual_Analysis]
                satisfied_by = Tools.ManualAnalysis
                description = '''The manual-analysis tooling shall reject a results file when `results` is an empty list.'''
            }

            ToolQualification.ToolRequirement ManualAnalysisResultsFinalEntryAssertionType {
                derived_from = [UseCases.Perform_Manual_Analysis]
                satisfied_by = Tools.ManualAnalysis
                description = '''The manual-analysis tooling shall reject a results file when the final entry in `results` is not a JSON object with `type` equal to `"assertion"`.'''
            }

            ToolQualification.ToolRequirement ManualAnalysisResultsFinalAssertionPassedTrue {
                derived_from = [UseCases.Perform_Manual_Analysis]
                satisfied_by = Tools.ManualAnalysis
                description = '''The manual-analysis tooling shall evaluate a results file as passing only when the final entry in `results` has `passed` equal to the boolean value `true`.'''
            }

            ToolQualification.ToolRequirement ManualAnalysisTestVerdictRule {
                derived_from = [UseCases.Perform_Manual_Analysis, UseCases.Detect_Stale_Manual_Analysis]
                satisfied_by = Tools.ManualAnalysis
                description = '''The manual-analysis test runner shall, if invoked without the `--allow-check-failures` flag, return a passing verdict only when both lock-file verification and results-file verification pass.'''
            }

        }

        section "Traceability Artifact" {

            ToolQualification.ToolRequirement ManualAnalysisLobsterArtifactGenerated {
                derived_from = [UseCases.Trace_Manual_Analysis_Evidence]
                satisfied_by = Tools.ManualAnalysis
                description = '''The manual-analysis test target shall generate one LOBSTER artifact file in `lobster-act-trace` format version 3.'''
            }

            ToolQualification.ToolRequirement ManualAnalysisLobsterSingleActivityItem {
                derived_from = [UseCases.Trace_Manual_Analysis_Evidence]
                satisfied_by = Tools.ManualAnalysis
                description = '''The generated LOBSTER artifact shall contain exactly one activity item identified by the Bazel label of the `manual_analysis` target.'''
            }

            ToolQualification.ToolRequirement ManualAnalysisLobsterRefsFromRequirements {
                derived_from = [UseCases.Trace_Manual_Analysis_Evidence]
                satisfied_by = Tools.ManualAnalysis
                description = '''The generated LOBSTER activity item `refs` list shall contain one entry of the form `req <identifier>` for each identifier in the analysis YAML `requirements` list.'''
            }

            ToolQualification.ToolRequirement ManualAnalysisLobsterStatusOk {
                derived_from = [UseCases.Trace_Manual_Analysis_Evidence]
                satisfied_by = Tools.ManualAnalysis
                description = '''The manual-analysis tooling shall set the LOBSTER activity `status` to `ok` when both lock-file verification and results-file verification pass.'''
            }

            ToolQualification.ToolRequirement ManualAnalysisLobsterStatusFail {
                derived_from = [UseCases.Trace_Manual_Analysis_Evidence]
                satisfied_by = Tools.ManualAnalysis
                description = '''The manual-analysis tooling shall set the LOBSTER activity `status` to `fail` when lock-file verification or results-file verification does not pass.'''
            }

            ToolQualification.ToolRequirement ManualAnalysisLobsterNotGeneratedOnRequirementsParseFailure {
                derived_from = [UseCases.Trace_Manual_Analysis_Evidence]
                satisfied_by = Tools.ManualAnalysis
                description = '''The manual-analysis test runner shall not generate a LOBSTER artifact when parsing the analysis YAML requirements fails.'''
            }

        }
    }
}
