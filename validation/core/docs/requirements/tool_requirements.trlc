/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Tools
import ToolQualification
import rules_score

section "Tool Requirements" {

    section "Validation Core" {

        section "Bazel Component Validator" {

            ToolQualification.ToolRequirement BazelComponentDependableElementConsistency {
                description = '''The validator shall report an error when a
                Bazel `dependable_element` target exists without a
                corresponding `package <<SEooC>>` in the PlantUML component
                diagram, or when a `package <<SEooC>>` exists without a
                corresponding Bazel `dependable_element` target.'''
                derived_from = [rules_score.Validate_Architecture_Specification_Documents]
                satisfied_by = Verifier
            }

            ToolQualification.ToolRequirement BazelComponentSingleRoot {
                description = '''The validator shall report an error before
                design matching when the architecture JSON contains other
                than exactly one root target entry, where a root is an entry
                whose full Bazel label is not referenced by any entry's
                `components` list. Empty input has zero roots. Distinct root
                labels count separately even when their design names are
                identical; for multiple roots, the error lists all root
                labels.'''
                derived_from = [rules_score.Validate_Architecture_Specification_Documents]
                satisfied_by = Verifier
            }

            ToolQualification.ToolRequirement BazelComponentComponentConsistency {
                description = '''The validator shall report an error when a
                Bazel `component` target exists under a dependable element
                without a corresponding `<<component>>` entity in PlantUML
                under the same parent, or when a `<<component>>` entity
                exists in PlantUML without a corresponding Bazel `component`
                target under the expected parent.'''
                derived_from = [rules_score.Validate_Architecture_Specification_Documents]
                satisfied_by = Verifier
            }

            ToolQualification.ToolRequirement BazelComponentUnitConsistency {
                description = '''The validator shall report an error when a
                Bazel `unit` target exists under a component without a
                corresponding `<<unit>>` entity in PlantUML under the same
                parent component, or when a `<<unit>>` entity exists in
                PlantUML without a corresponding Bazel `unit` target under
                the expected parent.'''
                derived_from = [rules_score.Validate_Architecture_Specification_Documents]
                satisfied_by = Verifier
            }

            ToolQualification.ToolRequirement BazelComponentNameCaseInsensitive {
                description = '''The validator shall match element names
                between Bazel and PlantUML case-insensitively, using the
                PlantUML name (the last segment of the entity id), and
                the effective `design_name` for Bazel `unit` and `component`
                targets, defaulting to the target's short name, or the
                `dependable_element` target name for the root. PlantUML
                aliases do not participate in matching.'''
                derived_from = [rules_score.Validate_Architecture_Specification_Documents]
                satisfied_by = Verifier
            }

            ToolQualification.ToolRequirement BazelComponentParentContext {
                description = '''The validator shall verify that each Bazel
                element and its PlantUML counterpart share the same parent
                context, identified by the full case-insensitive design path
                from the dependable element through all enclosing components
                to the immediate parent, rather than only the immediate
                parent's name. Bazel path segments use the dependable-element
                target name and each enclosing component's effective
                `design_name`. A shared Bazel component target is matched
                separately under every containing parent design path.'''
                derived_from = [rules_score.Validate_Architecture_Specification_Documents]
                satisfied_by = Verifier
            }

            ToolQualification.ToolRequirement BazelComponentNonEmptyComposition {
                description = '''The validator shall report an error when a
                Bazel `dependable_element` or `component` target decomposes
                into zero nested `component` or `unit` targets, even when the
                corresponding PlantUML entity likewise shows no nested
                elements.'''
                derived_from = [rules_score.Validate_Architecture_Specification_Documents]
                satisfied_by = Verifier
            }

        }

        section "Component Model Validator" {

            ToolQualification.ToolRequirement ComponentModelCrossFileDeclarationConsistency {
                description = '''When an entity with the same id is declared
                in more than one `static` PlantUML file, the validator shall
                report an error if the declarations disagree on stereotype or
                element type, and shall otherwise merge their relations into
                a single entity.'''
                derived_from = [rules_score.Validate_Architecture_Specification_Documents]
                satisfied_by = Verifier
            }

            ToolQualification.ToolRequirement ComponentModelSingleHomeDecomposition {
                description = '''The validator shall report an error when an
                entity's children are declared across more than one `static`
                PlantUML file and no single file declares the full set of
                children declared for that entity anywhere.'''
                derived_from = [rules_score.Validate_Architecture_Specification_Documents]
                satisfied_by = Verifier
            }

            ToolQualification.ToolRequirement ComponentModelAnchoring {
                description = '''The validator shall report an error when a
                `<<component>>` or `<<unit>>` is not nested directly under a
                `<<SEooC>>` or a `<<component>>`, naming its source location
                and any other declaration of the same name.'''
                derived_from = [rules_score.Validate_Architecture_Specification_Documents]
                satisfied_by = Verifier
            }

        }

        section "Component Sequence Validator" {

            ToolQualification.ToolRequirement ComponentSequenceIdentifierConsistency {
                description = '''The validator shall report an error when a
                unit defined in the component diagram is not referenced by
                any participant in the sequence diagrams, when a participant
                uid in a sequence diagram does not match any unit, component
                or SEooC id in the component diagram, or when a participant
                uid matches multiple unit ids or multiple component ids
                ambiguously. A participant that matches a component or SEooC
                is a black box and shall not count as a reference to the
                units it contains.'''
                derived_from = [rules_score.Validate_Architecture_Specification_Documents]
                satisfied_by = Verifier
            }

            ToolQualification.ToolRequirement ComponentSequenceInterfaceConnectionConsistency {
                description = '''The validator shall report an error when two
                units are connected through an interface in the component
                diagram but no function-call interaction between exactly
                those two units appears in any sequence diagram, or when a
                function call between elements appears in a sequence diagram
                but the component diagram does not define a shared interface
                between them. The interfaces of a component or SEooC
                participant are the interfaces of the units it contains, and
                a call with a component or SEooC participant shall not count
                as a function-call interaction between the units it
                contains.'''
                derived_from = [rules_score.Validate_Architecture_Specification_Documents]
                satisfied_by = Verifier
            }

        }

        section "Sequence Diagram Semantics" {

            ToolQualification.ToolRequirement SequenceEnvironmentParticipants {
                description = '''The validators shall treat a sequence
                participant declared as `actor` or with the `<<external>>`
                stereotype (in any letter case) as part of the environment:
                it shall not be required to match a unit, class or component,
                and messages to or from it shall not be checked against unit
                interfaces. Such a declaration in any sequence diagram shall
                apply to the participant uid in all sequence diagrams, and the
                validator shall report an error when one uid is declared as an
                actor in one place and as `<<external>>` in another, or when
                an environment participant uses the uid of a unit, component
                or SEooC of the component diagram.'''
                derived_from = [rules_score.Validate_Architecture_Specification_Documents]
                satisfied_by = Verifier
            }

            ToolQualification.ToolRequirement SequenceMessageKinds {
                description = '''The validators shall treat only
                synchronous and asynchronous messages as operation calls.
                Only the `>>` and `<<` arrowheads shall make a message
                asynchronous. Reply messages and messages with the create
                (`**`) or delete (`!!`) marker shall not be matched against an
                API and shall not count for interface coverage. A `create`
                statement shall not change the kind of a message.'''
                derived_from = [rules_score.Validate_Architecture_Specification_Documents]
                satisfied_by = Verifier
            }

            ToolQualification.ToolRequirement SequenceGateMessages {
                description = '''The validators shall treat a message
                without sender or receiver as a call from or to an unspecified
                environment. A message from such an environment to an element
                shall use a method declared on an interface the called
                element provides, in the internal API or the public API, and
                shall count as a use of that method for interface coverage
                only when it does. A message to such an environment shall not
                be checked against an API and shall not count for interface
                coverage.'''
                derived_from = [rules_score.Validate_Architecture_Specification_Documents]
                satisfied_by = Verifier
            }

            ToolQualification.ToolRequirement SequencePublicApiBoundary {
                description = '''When a public API is provided, the
                validator shall report an error when a call from an actor to
                an element of the SEooC uses a method not declared on a public
                API interface the element provides, or when a callback from an
                element of the SEooC to an actor is labelled with neither the
                name of a public API interface the element requires nor one of
                its methods, whether or not internal API diagrams are
                provided. The scope of an element shall follow its interface
                roles in the component diagram; without a component diagram or
                a bound public interface, the whole public API shall be used by
                name.'''
                derived_from = [rules_score.Validate_Architecture_Specification_Documents]
                satisfied_by = Verifier
            }

        }

        section "Sequence Internal API Validator" {

            ToolQualification.ToolRequirement ComponentSequenceInternalApiMethodNameConsistency {
                description = '''When component, sequence, and internal API
                diagrams are provided, the validator shall report an error
                when a function used in a sequence interaction is not declared
                in any shared interface of the participating units as defined
                in the component diagram. A call with a component or SEooC
                participant shall pass when the function is declared, in the
                internal API or the public API, on an interface shared by both
                ends; the interface roles of such a call shall not be
                checked.'''
                derived_from = [rules_score.Validate_Architecture_Specification_Documents]
                satisfied_by = Verifier
            }

            ToolQualification.ToolRequirement ComponentSequenceInternalApiConsumerProviderRoleConsistency {
                description = '''When component, sequence, and internal API
                diagrams are provided, the validator shall report an error
                when a cross-unit sequence interaction does not match
                consumer/provider roles derived from the shared interfaces in
                the component diagram: the caller shall require and the callee
                shall provide an interface on which the called method is
                declared.'''
                derived_from = [rules_score.Validate_Architecture_Specification_Documents]
                satisfied_by = Verifier
            }

            ToolQualification.ToolRequirement ComponentSequenceInternalApiInterfaceCoverage {
                description = '''When component, sequence, and internal API
                diagrams are provided, the validator shall report an error
                when a function declared in a validated interface is never
                called in any sequence interaction. Self-calls count as valid
                usage; calls with an actor or external system, calls to a
                gate and rejected gate messages do not.'''
                derived_from = [rules_score.Validate_Architecture_Specification_Documents]
                satisfied_by = Verifier
            }

            ToolQualification.ToolRequirement InternalApiInterfaceMerge {
                description = '''When an interface is declared in more than
                one internal API file, the validator shall treat it as one
                interface holding the union of the methods declared in all
                of its declarations.'''
                derived_from = [rules_score.Validate_Architecture_Specification_Documents]
                satisfied_by = Verifier
            }

        }

        section "Component Internal API Validator" {

            ToolQualification.ToolRequirement ComponentInternalApiInterfaceDeclarationConsistency {
                description = '''The validator shall report an error when an
                interface declared in the component diagram is not declared as
                an interface in the internal API diagram.'''
                derived_from = [rules_score.Validate_Architecture_Specification_Documents]
                satisfied_by = Verifier
            }

        }

        section "Component Public API Validator" {

            ToolQualification.ToolRequirement ComponentPublicApiInterfaceDeclarationConsistency {
                description = '''The validator shall report an error when a
                public API interface declared in the component diagram is not
                declared as an interface in the public API class diagram.'''
                derived_from = [rules_score.Validate_Architecture_Specification_Documents]
                satisfied_by = Verifier
            }

            ToolQualification.ToolRequirement ComponentPublicApiSeoocRelationshipConsistency {
                description = '''The validator shall report an error when a
                public API interface declared in the component diagram is not
                connected by an interface-binding relationship from the SEooC
                in the component diagram.'''
                derived_from = [rules_score.Validate_Architecture_Specification_Documents]
                satisfied_by = Verifier
            }

        }

        section "Class Design Implementation Validator" {

            ToolQualification.ToolRequirement ClassDesignImplementationEntityConsistency {
                description = '''The validator shall report an error when an
                entity modeled in the unit design class diagram has no
                corresponding entity in the implementation class diagram, or
                when the matching implementation entity differs in entity
                type. Consistency of type aliases, variables, methods, enum
                literals, relationships, and template parameters is specified
                by the dedicated requirements below.'''
                derived_from = [rules_score.Validate_Unit_Specification_Documents]
                satisfied_by = Verifier
            }

            ToolQualification.ToolRequirement ClassDesignImplementationDeclarationMerge {
                description = '''When the same class id is declared more than
                once across the unit design class diagrams, the validator
                shall merge the declarations and unite their relationships if
                at most one of them has a body, and shall report an error when
                two declarations have a body or when their entity type or
                stereotype differs.'''
                derived_from = [rules_score.Validate_Unit_Specification_Documents]
                satisfied_by = Verifier
            }

            ToolQualification.ToolRequirement ClassDesignImplementationTemplateParameterConsistency {
                description = '''The validator shall report an error when
                template parameters modeled on a unit design entity or method
                differ from the template parameters on the matching
                implementation entity or method, except for class template
                parameters of implementation partial and explicit full
                specializations. These specializations are matched by fully
                qualified base name only; their specialization arguments are
                not validated against the design. Method template parameters
                remain subject to this consistency check. When matching partial
                or explicit full specializations exist, a matching primary
                template is included in implementation consistency checks only
                if its template parameters match the design. Without matching
                specializations, the primary template is checked normally,
                including template-parameter mismatches. Ordinary non-template
                classes are not subject to this primary-template filtering
                rule.'''
                derived_from = [rules_score.Validate_Unit_Specification_Documents]
                satisfied_by = Verifier
            }

            ToolQualification.ToolRequirement ClassDesignImplementationTypeAliasConsistency {
                description = '''The validator shall report an error when a
                type alias modeled in a unit design entity is missing from the
                matching implementation entity, or when the matching
                implementation type alias differs in original type.'''
                derived_from = [rules_score.Validate_Unit_Specification_Documents]
                satisfied_by = Verifier
            }

            ToolQualification.ToolRequirement ClassDesignImplementationVariableConsistency {
                description = '''The validator shall report an error when a
                variable modeled in a unit design entity is missing from the
                matching implementation entity, or when the matching
                implementation variable differs in data type, visibility, or
                static flag.'''
                derived_from = [rules_score.Validate_Unit_Specification_Documents]
                satisfied_by = Verifier
            }

            ToolQualification.ToolRequirement ClassDesignImplementationMethodConsistency {
                description = '''The validator shall report an error when a
                method modeled in a unit design entity is missing from the
                matching implementation entity, or when the matching
                implementation method differs in return type, visibility,
                parameters, or method modifiers (`static`, `virtual`,
                `abstract`, `override`, constructor, destructor, or
                `noexcept`).'''
                derived_from = [rules_score.Validate_Unit_Specification_Documents]
                satisfied_by = Verifier
            }

            ToolQualification.ToolRequirement ClassDesignImplementationEnumLiteralConsistency {
                description = '''The validator shall report an error when an
                enum literal modeled in a unit design enum is missing from the
                matching implementation enum, or when the matching
                implementation enum literal data differs from the unit design.'''
                derived_from = [rules_score.Validate_Unit_Specification_Documents]
                satisfied_by = Verifier
            }

            ToolQualification.ToolRequirement ClassDesignImplementationRelationshipConsistency {
                description = '''The validator shall report an error when a
                relationship modeled in a unit design entity is missing from
                the matching implementation entity, or when the matching
                implementation relationship differs in source, target, or
                relationship type.'''
                derived_from = [rules_score.Validate_Unit_Specification_Documents]
                satisfied_by = Verifier
            }

            ToolQualification.ToolRequirement ClassDesignImplementationFreeFunctionConsistency {
                description = '''The validator shall report an error when a
                free function modeled in the unit design is missing from the
                implementation, or when the matching implementation free
                function differs in return type, parameters, or template
                parameters.'''
                derived_from = [rules_score.Validate_Unit_Specification_Documents]
                satisfied_by = Verifier
            }

            ToolQualification.ToolRequirement ClassDesignImplementationTypeNormalization {
                description = '''The validator shall normalize namespace
                separators, the `std::` type prefix, and pointer or reference
                spacing before comparing entity references and type names
                between unit design and implementation class diagrams.'''
                derived_from = [rules_score.Validate_Unit_Specification_Documents]
                satisfied_by = Verifier
            }

            ToolQualification.ToolRequirement ClassDesignImplementationTopLevelConstParameters {
                description = '''The validator shall ignore top-level `const`
                on method and free function parameters when comparing unit
                design and implementation parameter types, and shall continue
                to report a mismatch for low-level `const` (for example
                `const int*` versus `int*`). The validator shall not ignore
                top-level `const` on return types, variable data types, or
                type alias original types.'''
                derived_from = [rules_score.Validate_Unit_Specification_Documents]
                satisfied_by = Verifier
            }

        }

        section "Class Design Sequence Validator" {

            ToolQualification.ToolRequirement ClassDesignSequenceParticipantClassConsistency {
                description = '''The validator shall report an error when a
                sequence participant that represents a designed runtime
                element has no matching class in the unit design class
                diagram, or when the participant matches multiple design
                classes ambiguously.'''
                derived_from = [rules_score.Validate_Unit_Specification_Documents]
                satisfied_by = Verifier
            }

            ToolQualification.ToolRequirement ClassDesignSequenceMessageOperationConsistency {
                description = '''The validator shall report an error when a
                message or self-call in a sequence diagram targets a design
                class that neither declares nor inherits the called
                operation through its base classes or interfaces. The
                comparison shall match at least the operation name and may
                additionally compare parameter arity and normalized parameter
                types when both diagrams provide that information.'''
                derived_from = [rules_score.Validate_Unit_Specification_Documents]
                satisfied_by = Verifier
            }

        }

    }

}
